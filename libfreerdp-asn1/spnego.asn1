SPNEGO DEFINITIONS ::=

BEGIN

MechType ::= OBJECT IDENTIFIER
MechTypeList ::= SEQUENCE OF MechType

NegotiationToken ::= CHOICE {
	negTokenInit    [0] NegTokenInit,
	negTokenResp    [1] NegTokenResp
}

NegTokenInit ::= SEQUENCE {
	mechTypes       [0] MechTypeList,
	reqFlags        [1] ContextFlags  OPTIONAL,
	mechToken       [2] OCTET STRING  OPTIONAL,
	mechListMIC     [3] OCTET STRING  OPTIONAL
}

ContextFlags ::= BIT STRING {
	delegFlag       (0),
	mutualFlag      (1),
	replayFlag      (2),
	sequenceFlag    (3),
	anonFlag        (4),
	confFlag        (5),
	integFlag       (6)
} (SIZE (32))

NegHints ::= SEQUENCE {
	hintName[0] GeneralString OPTIONAL,
	hintAddress[1] OCTET STRING OPTIONAL
}

NegTokenInit2 ::= SEQUENCE {
	mechTypes[0] MechTypeList OPTIONAL,
	reqFlags [1] ContextFlags OPTIONAL,
	mechToken [2] OCTET STRING OPTIONAL,
	negHints [3] NegHints OPTIONAL,
	mechListMIC [4] OCTET STRING OPTIONAL
}

NegTokenResp ::= SEQUENCE {
	negState[0] ENUMERATED {
		accept-completed    (0),
		accept-incomplete   (1),
		reject              (2),
		request-mic         (3)
          }                                 OPTIONAL,
          supportedMech   [1] MechType      OPTIONAL,
          responseToken   [2] OCTET STRING  OPTIONAL,
          mechListMIC     [3] OCTET STRING  OPTIONAL
}

END
